module sc-interface-set-flags {
	yang-version 1;
    namespace "urn:sweetcomb:params:xml:ns:yang:vpp:interface:set-flags";
    prefix "sc-interface-set-flags";
	
	import ietf-inet-types {
        prefix "inet";
    }

    organization "HUACHENTEL";

    description
    "This module contains a collection of YANG definitions for
     managing interface flags in VPP.

     Copyright (c) 2018 HUACHENTEL and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

    revision "2018-10-31" {
        description "set interface flags";
    }
	
	container sc-interface-set-flags {
		leaf sw-if-index{
			type uint32;
			description "the index of a interface";
			mandatory true;
		}
		leaf admin-up-down{
			type uint8;
			description "state of a interface ";
			default 1;			
		}
	}
}
