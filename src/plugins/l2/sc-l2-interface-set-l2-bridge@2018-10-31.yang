module sc-l2-interface-set-l2-bridge {
	yang-version 1;
    namespace "urn:sweetcomb:params:xml:ns:yang:vpp:l2:interface-set-l2-bridge";
    prefix "sc-l2-interface-set-l2-bridge";
	
	import ietf-inet-types {
        prefix "inet";
    }

    organization "HUACHENTEL";

    description
    "This module contains a collection of YANG definitions for
     managing interface flags in VPP.

     Copyright (c) 2018 HUACHENTEL and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

    revision "2018-10-31" {
        description "add interface into | out bridge";
    }
	
	container sc-l2-interface-set-l2-bridge {
		leaf rx-sw-if-index{
			type uint32;
			description "the index of a interface";
			mandatory true;
		}
		leaf bd-id{
			type uint32;
			description "the key of bridge domain";
			mandatory true;
		}
		leaf shg{
			type uint8 {
				range "0..1";
			}
			description "";
			default 0;
		}
		leaf bvi{
			type uint8 {
				range "0..1";
			}
			description "is bvi ?";
			default 0;
		}
		leaf enable{
			type uint8 {
				range "0..1";
			}
			description "is in or out";
			default 1;
		}
		
	}
}
