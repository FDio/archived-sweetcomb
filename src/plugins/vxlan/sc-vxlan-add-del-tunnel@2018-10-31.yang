module sc-vxlan-add-del-tunnel {
	yang-version 1;
    namespace "urn:sweetcomb:params:xml:ns:yang:vpp:vxlan:add-del";
    prefix "sc-vxlan-add-del-tunnel";
	
	import ietf-inet-types {
        prefix "inet";
    }

    organization "HUACHENTEL";

    description
    "This module contains a collection of YANG definitions for
     managing vxlan based ACLs in VPP.

     Copyright (c) 2018 HUACHENTEL and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

    revision "2018-10-31" {
        description "vxlan add del tunnel";
    }
	
	rpc sc-vxlan-add-del-tunnel {
		input {
			leaf is-add{
				type uint8 {
					range "0..1";
				}
				mandatory true;
			}
			leaf is-ipv6{
				type uint8 {
        	                        range "0..1";
	                        }
				default 0;
			}
			leaf instance{
				type int32;
				description "vxlan instance";
				default -1;
			}
			
			leaf src-address{
				type inet:ip-address;
				description "src address";
			}
			leaf dst-address{
				type inet:ip-address;
				description "src address";
			}
			leaf mcast-sw-if-index{
				type uint32;
				description "";
				default 0xFFFFFFFF;
			}
			leaf encap-vrf-id{
				type uint32;
				description "";
				default 0;
			}
			leaf decap-next-index{
				type uint32;
				description "";
				default 1;
			}
			leaf vni{
				type uint32{
					range "0..16777215";
				}
				description "vxlan vni";
			}
		}
		
		output {
			leaf retval {
				type int32;
				description "return value";
			}
			leaf sw_if_index {
				type uint32;
				description "return value";
			}
		}
	}
}
